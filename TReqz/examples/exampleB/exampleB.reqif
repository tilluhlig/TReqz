# Specification Title

# Specification: Specification Document
- Description: Requirements Document

## R1: A
every column filled
- bool_column: true
- string_column: text
- integer_column: 4
- real_column: 4.0
- date_column: 2019-02-23T11:27:58.000+01:00
- xhtml_column: text text2 text3Â
- enumeration_column_multi: B, C
- bool_column_default: true
- string_column_default: test
- integer_column_default: 1
- real_column_default: 2.0
- date_column_default: 2004-04-12T13:20:00.000+02:00

## R2: B
nothing filled
- bool_column_default: true
- string_column_default: test
- integer_column_default: 1
- real_column_default: 2.0
- date_column_default: 2004-04-12T13:20:00.000+02:00

## R3: C
default values filled
- bool_column_default: false
- string_column_default: other
- integer_column_default: 2
- real_column_default: 3.0
- date_column_default: 2004-04-24T01:20:00.000+02:00

## R4: D
filled like default
- bool_column_default: true
- integer_column_default: 1
- real_column_default: 2.0
- date_column_default: 2004-04-12T13:20:00.000+02:00
- string_column_default: test

### R5: E
dummyE
- bool_column_default: true
- string_column_default: test
- integer_column_default: 1
- real_column_default: 2.0
- date_column_default: 2004-04-12T13:20:00.000+02:00

#### R8: F
dummyF
- bool_column_default: true
- string_column_default: test
- integer_column_default: 1
- real_column_default: 2.0
- date_column_default: 2004-04-12T13:20:00.000+02:00

##### R10: G
dummyG
- bool_column_default: true
- string_column_default: test
- integer_column_default: 1
- real_column_default: 2.0
- date_column_default: 2004-04-12T13:20:00.000+02:00

#### R9: H
dummyH
- bool_column_default: true
- string_column_default: test
- integer_column_default: 1
- real_column_default: 2.0
- date_column_default: 2004-04-12T13:20:00.000+02:00

### R6: I
dummyI
- bool_column_default: true
- string_column_default: test
- integer_column_default: 1
- real_column_default: 2.0
- date_column_default: 2004-04-12T13:20:00.000+02:00

#### R7: J
dummyJ
- bool_column_default: true
- string_column_default: test
- integer_column_default: 1
- real_column_default: 2.0
- date_column_default: 2004-04-12T13:20:00.000+02:00

## R11: K
dummyK
- bool_column_default: true
- string_column_default: test
- integer_column_default: 1
- real_column_default: 2.0
- date_column_default: 2004-04-12T13:20:00.000+02:00
